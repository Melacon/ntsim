module org-openroadm-flexogroup-capability {
  namespace "http://org/openroadm/flexogroup-capability";
  prefix org-openroadm-flexogroup-capability;

  import org-openroadm-device {
    prefix org-openroadm-device;
    revision-date 2019-11-29;
  }
  import org-openroadm-common-optical-channel-types {
    prefix org-openroadm-common-optical-channel-types;
    revision-date 2019-11-29;
  }
  import org-openroadm-port-types {
    prefix org-openroadm-port-types;
    revision-date 2019-11-29;
  }
  import org-openroadm-port-capability {
    prefix org-openroadm-port-capability;
    revision-date 2019-11-29;
  }

  organization
    "Open ROADM MSA";
  contact
    "OpenROADM.org";
  description
    "YANG definitions for Flexogroup capabilities.

     Copyright of the Members of the Open ROADM MSA Agreement dated (c) 2018,
     All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.

     Also contains code components extracted from IETF Interfaces.  These code components
     are copyrighted and licensed as follows:

     Copyright (c) 2018 IETF Trust and the persons identified as the document authors.
     All rights reserved.

     This document is subject to BCP 78 and the IETF Trust's Legal Provisions Relating
     to IETF Documents (http://trustee.ietf.org/license-info) in effect on the date of
     publication of this document. Please review these documents carefully, as they
     describe your rights and restrictions with respect to this document. Code Components
     extracted from this document must include Simplified BSD License text as described in
     Section 4.e of the Trust Legal Provisions and are provided without warranty as
     described in the Simplified BSD License.";

  revision 2019-11-29 {
    description
      "Version 6.1.0";
  }
  revision 2019-09-27 {
    description
      "Version 6.0.0";
  }
  revision 2019-05-31 {
    description
      "Version 5.1.0";
  }
  revision 2019-03-29 {
    description
      "Version 5.0.0";
  }
  revision 2018-11-30 {
    description
      "Version 4.1.0";
  }
  revision 2018-09-28 {
    description
      "Version 4.0.0";
  }
  revision 2018-05-30 {
    description
      "Version 3.1.0";
  }
  revision 2018-05-30 {
    description
      "Version 3.1.0";
    reference "V3.1.0";
  }
  revision 2018-03-30 {
    description
      "Version 3.0.0";
    reference "V3.0.0";
  }

  identity flexo-modulation-format-identity {
    description
      "Flexo modulation format identification";
  }

  grouping flexo-grp {
    description
      "Flexo group";
    leaf circuit-pack-name {
      type leafref {
        path "/org-openroadm-device:org-openroadm-device/org-openroadm-device:circuit-packs/org-openroadm-device:circuit-pack-name";
      }
      description
        "Circuit-Pack identifier. Unique within the context of a device.";
    }
    leaf port-name {
      type leafref {
        path "/org-openroadm-device:org-openroadm-device/org-openroadm-device:circuit-packs/org-openroadm-device:ports/org-openroadm-device:port-name";
      }
      description
        "Port index identifier. Unique within the context of a circuit-pack.";
    }
    leaf fec {
      type identityref {
        base org-openroadm-common-optical-channel-types:fec-identity;
      }
      status deprecated;
      description
        "Flexo FEC";
    }
    leaf otsi-rate {
      type identityref {
        base org-openroadm-common-optical-channel-types:flexo-otsi-rate-identity;
      }
      mandatory true;
      description
        "Flexo rate";
    }
    leaf otsi-modulation-format {
      type identityref {
        base flexo-modulation-format-identity;
      }
      description
        "Flexo modulation format";
    }
    leaf otsi-width {
      type uint16;
      description
        "OTSI width";
    }
    leaf operational-mode-id {
      type string;
      mandatory true;
      description
        "Optical profile operational mode identifier";
    }
  }

  grouping flexogroup-capability-grp {
    description
      "Flexogroup group capability";
    container flexogroup-capabilities {
      config false;
      description
        "Flexo group capabilities";
      list flexogroup-capability-group {
        key "flexogroup-capability-id";
        description
          "Flexogroup capability";
        leaf flexogroup-capability-id {
          type uint16;
          description
            "Flexogroup capability group id";
        }
        leaf if-cap-type {
          type identityref {
            base org-openroadm-port-types:supported-if-capability;
          }
          description
            "Interface type/hierarchy/rate supported on this Flexo port";
        }
        container logical-port {
          leaf circuit-pack-name {
            type string;
            description
              "The circuit pack supporting the logical port";
          }
          leaf port-name {
            type string;
            description
              "Upon the group creation (i.e., otsig or flexogroup), independent of one member or multiple members in the group, NE device shall inherently auto-create the logical port on one of existing circuit packs. NE shall ensure unique naming (logical port) with respect to the other ports on the associated circuit pack.";
          }
        }
        container otn-capability {
          description
            "OTN capability";
          uses org-openroadm-port-capability:otn-capability-grp;
        }
        leaf foic-type {
          type identityref {
            base org-openroadm-common-optical-channel-types:foic-identity;
          }
          description
            "FlexO interface type ";
        }
        container ho-odu-mux-hierarchy {
          description
            "High order ODU mux hierarchy ";
          uses org-openroadm-port-capability:odu-mux-hierarchy-grp;
        }
        list supported-otucn-rate {
          key "oducn-index";
          status deprecated;
          description
            "Supported OTUCn rate";
          leaf oducn-index {
            type uint16;
            description
              "ODUCn rate index";
          }
          leaf otucn-n-rate {
            type uint16;
            description
              "Specify the N associated with OTUCn, e.g. N = 2,3,4 for 200G/300G/400G respectively";
          }
          list flexo {
            key "circuit-pack-name port-name";
            description
              "Flexo group";
            uses flexo-grp;
          }
        }
      }
    }
  }

  augment "/org-openroadm-device:org-openroadm-device" {
    description
      "augment for Flexo group capability";
    uses flexogroup-capability-grp;
  }
}
